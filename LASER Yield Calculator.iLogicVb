Sub Main()
	
	sheetWidth= iProperties.Value("Custom", "SheetWidth")
	sheetLength= iProperties.Value("Custom", "SheetLength")
	sheetTotalAvailableWidth = sheetWidth - (CLAMP + WEB)
	sheetTotalAvailableLength = sheetLength - (WEB * 2)
	
	Dim calculationX As Integer = calculatePartsHorizontally()
	Dim calculationY As Integer = calculatePartsVartically()
	
	If calculationX >= calculationY Then
		MessageBox.Show("LASER  :  " + CStr(calculationX) + "  pcs", "Yields X")
	Else
		MessageBox.Show("LASER  :  " + CStr(calculationY) + "  pcs", "Yields Y")
	End If
	
End Sub


Private Const KERF As Double = .120
Private Const WEB As Double = .750
Private Const CLAMP As Double = 1.500

Private sheetWidth As Integer
Private sheetLength As Integer
Private sheetTotalAvailableWidth As Double
Private sheetTotalAvailableLength As Double

Function calculatePartsHorizontally() As Integer

	Dim partWidth As Double = SheetMetal.FlatExtentsWidth
	Dim partLength As Double = SheetMetal.FlatExtentsLength
	
	Dim partWidthPlus As Double = partWidth + KERF
	Dim partLengthPlus As Double = partLength + KERF

	Dim partsY As Double  = sheetTotalAvailableWidth / partWidthPlus
	Dim partsX As Double = sheetTotalAvailableLength / partLengthPlus

	Dim partsYasInt As Integer = Int(partsY)
	Dim partsXasInt As Integer = Int(partsX)

	Dim totalSheetUsageX As Double = partsXasInt * partLengthPlus
	Dim totalSheetUsageY As Double = partsYasInt * partWidthPlus
	
	Dim extraMaterialOnXdirection As Double = sheetTotalAvailableLength - totalSheetUsageX

	If extraMaterialOnXdirection > partWidthPlus And PartLengthPlus < sheetTotalAvailableWidth Then	
		
		Dim extraPartsOnX As Double = extraMaterialOnXdirection / partWidthPlus
		Dim extraPartsOnY As Double = sheetTotalAvailableWidth / partLengthPlus
		Dim totalExtraParts As Integer = Int(extraPartsOnX) * Int(extraPartsOnY)
		
		Dim totalParts As Integer = partsXasInt * partsYasInt
		
		Dim totalPartsPlus As Integer = totalExtraParts + totalParts
		Return totalPartsPlus
		
	
	Else
	
		Dim totalParts As Integer = partsXasInt * partsYasInt		
		Return totalParts	
	End If
	
End Function

Function calculatePartsVartically() As Integer

	Dim partWidth As Double = SheetMetal.FlatExtentsWidth
	Dim partLength As Double = SheetMetal.FlatExtentsLength
	
	Dim partWidthPlus As Double = partWidth + KERF
	Dim partLengthPlus As Double = partLength + KERF

	Dim partsY As Double  =  sheetTotalAvailableWidth / partLengthPlus
	Dim partsX As Double = sheetTotalAvailableLength / partWidthPlus

	Dim partsYasInt As Integer = Int(partsY)
	Dim partsXasInt As Integer = Int(partsX)

	Dim totalSheetUsageX As Double = partsXasInt * partWidthPlus
	Dim totalSheetUsageY As Double = partsYasInt * partLengthPlus
	
	Dim extraMaterialOnYdirection As Double = sheetTotalAvailableWidth - totalSheetUsageY

	If extraMaterialOnYdirection > partWidthPlus Then	
		
		Dim extraPartsOnY As Double = extraMaterialOnYdirection / partWidthPlus
		Dim extraPartsOnX As Double = sheetTotalAvailableLength / partLengthPlus
		Dim totalExtraParts As Integer = Int(extraPartsOnX) * Int(extraPartsOnY)
		Dim totalParts As Integer = partsXasInt * partsYasInt
		
		Dim totalPartsPlus As Integer = totalExtraParts + totalParts
		Return totalPartsPlus

	Else
	
		Dim totalParts As Integer = partsXasInt * partsYasInt	
		Return totalParts
		
	End If
	
End Function
